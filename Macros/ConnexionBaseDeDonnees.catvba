Attribute VB_Name = "Assemblage"
'
'VARIABLES GENERALES Utiliser dans plusieurs macros
'

'différentes largeur pour chaque module
Public largeurAssemblageLigne As Integer
Public largeurAssemblageAngle As Integer

'compteur de nombre de module de chaque type pour les string des chemins
Public nPB1 As Integer
Public nPB2 As Integer
Public nPH1 As Integer
Public nBA1 As Integer

'TODO à remplacer par une fonction automatique
Public nombreModule As Long

'pour lancer l'incrémentation au prochain module
Public prochainOffsetLigne As Integer
Public prochainOffsetAngle As Integer

'Pour sauvegarder a profondeur générique
Public profondeurGeneral As Integer

'Pour la longueur des plans de travails
Public longueurPrimaire As Integer
Public longueurSecondaire As Integer

'Pour configurer la hauteur du plan de travail
Public hauteurGeneral As Integer

'Nom complet du module assemblé pour le nom des contraintes
Public moduleAssemble As String

'
'ASSEMBLAGE Modules standard sans position particulières (La majorité des modules)
'
Public Sub splitAssemblage()

    'initialisation du nombre de module de chaque catégorie à 0 pour remplir les string ensuite, pour compter les modules de chaque catégories déjà assemblé
    nPB1 = 0
    nPB2 = 0
    nPH1 = 0
    nBA1 = 0
    
    'premier module placé à 0
    prochainOffsetLigne = 0
    prochainOffsetAngle = 0
    
    'Mise à 0 des longeur de base du plan de travail
    longueurPrimaire = 0
    longueurSecondaire = 0
    
    Dim i As Integer 'compteur pour la boucle for
    
    For i = 0 To nombreModule 'Pour faire l'insertion de tous les modules
        
        Select Case module(i, 0) 'check du type de module pour paramétrer l'assemblage
            Case 1 'Placard bas modèle 1
                nPB1 = nPB1 + 1
                moduleAssemble = "Placard_Bas." & nPB1
                Call PositionPlacard(i)
                
            Case 2 'Placard bas modèle 2
                nPB2 = nPB2 + 1
                moduleAssemble = "Placard_Bas_2." & nPB2
                Call PositionPlacard(i)
                
            Case 3 'Bar
                MsgBox "Chef j'ai pas codé l'assemblage du bar"
                
            Case 4 'Placard haut modèle 1
                nPH1 = nPH1 + 1
                moduleAssemble = "Placard_Haut_1." & nPH1
                Call PositionPlacard(i)
                
            Case Else 'ça doit pas arriver normalement
                MsgBox "ERREUR type de module inconnu dans le début de l'assemblage check des modules"
                
        End Select
        
        Call ajoutOptions(i, module(i, 2), module(i, 3), module(i, 4)) 'ajout des options pour le module demandé
    Next
End Sub

'
'Vérification des options à ajouter pour chaque module
'
Public Sub ajoutOptions(module As Integer, option1 As String, option2 As String, option3 As String)
    If ((module = 1 Or module = 2) And option2 <> "0" And nBA1 = 0) Then 'insertion d'un bar sur les placard bas
        nBA1 = 1 'incrémentation du nombre de bar dans l'assemblage
        Call barModele1 'insertion du bar
        moduleAssemble = "Bar." & nBA1
        Call PositionPlacard(module)
    End If
End Sub


'
'Positionnement Placard
'
Public Sub PositionPlacard(numModule As Integer)
    
    If (module(numModule, 1) = "L") Then 'Si on souhaite avoir le module suivant la ligne
        'Indications sur quel produit on va travailler (toujours le même)
        Dim productDocument1 As ProductDocument
        Set productDocument1 = CATIA.ActiveDocument
        Dim productMain As Product
        Set productMain = productDocument1.Product
        'Indications comme quoi on va faire une contrainte d'asemblage
        Dim constraints1 As Constraints
        Set constraints1 = productMain.Connections("CATIAConstraints")
        '
        'GAUCHE
        '
        'Référencement des deux produits à assembler
        Dim productPart1 As Product
        Set productPart1 = CATIA.ActiveDocument.Product.Products.Item(moduleAssemble)
        Dim productPart2 As Product
        Set productPart2 = CATIA.ActiveDocument.Product.Products.Item("Squelette.1")
        'Référencement des publications utilisées
        'Element 1
        Dim Pub1 As Publication
        Set Pub1 = productPart1.Publications.Item("Gauche")
        Dim ref1 As reference
        Set ref1 = Pub1.Valuation
        'Element 2
        Dim Pub2 As Publication
        Set Pub2 = productPart2.Publications.Item("GAUCHE_PRIMAIRE")
        Dim ref2 As reference
        Set ref2 = Pub2.Valuation
        'Mise en place de la contrainte
        Dim constraint1 As Constraint
        Set constraint1 = constraints1.AddBiEltCst(catCstTypeDistance, ref1, ref2)
        'Contrainte de distance
        Dim length1 As Length
        Set length1 = constraint1.Dimension
        
        If (moduleAssemble = "Placard_Haut_1." & nPH1) Then 'Placard Haut
            length1.Value = 1000 * -1 'TODO Mettre une valeur choisi par l'utilisateur
        ElseIf (moduleAssemble = "Bar." & nBA1) Then
            length1.Value = 0 * -1 'TODO mettre une valeur avec un offset
        Else
            length1.Value = prochainOffsetLigne * -1
            prochainOffsetLigne = moduleLargeur(numModule, 0)
            longueurPrimaire = moduleLargeur(numModule, 0)
        End If
        
        constraint1.Orientation = catCstOrientSame
        
        '
        'DERRIERE EN LIGNE
        '
        Set constraints1 = productMain.Connections("CATIAConstraints")
        'Référencement des publications utilisées
        'Element 1
        Dim Pub3 As Publication
        Set Pub3 = productPart1.Publications.Item("Derriere")
        Dim ref3 As reference
        Set ref3 = Pub3.Valuation
        'Element 2
        Dim Pub4 As Publication
        Set Pub4 = productPart2.Publications.Item("DERRIERE")
        Dim ref4 As reference
        Set ref4 = Pub4.Valuation
        'Mise en place de la contrainte
        Dim constraint2 As Constraint
        Set constraint2 = constraints1.AddBiEltCst(catCstTypeDistance, ref3, ref4)
        'Contrainte de distance
        Dim length2 As Length
        Set length2 = constraint2.Dimension
        
        If (moduleAssemble = "Bar." & nBA1) Then 'Bar
            length2.Value = 150 'TODO Mettre une valeur choisi par l'utilisateur
            constraint2.Orientation = catCstOrientOpposite
        Else
            length2.Value = 0
            constraint2.Orientation = catCstOrientSame
        End If
        
    
    ElseIf (module(numModule, 1) = "A") Then 'Si on souhaite avoir le module suivant l'angle
    
        'Indications sur quel produit on va travailler (toujours le même)
        Set productDocument1 = CATIA.ActiveDocument
        Set productMain = productDocument1.Product
        Set productsMain = productMain.Products
        'Indications comme quoi on va faire une contrainte d'asemblage
        Set constraints1 = productMain.Connections("CATIAConstraints")
        '
        'DROITE
        '
        'Référencement des deux produits à assembler
        Set productPart1 = CATIA.ActiveDocument.Product.Products.Item(moduleAssemble)
        Set productPart2 = CATIA.ActiveDocument.Product.Products.Item("Squelette.1")
        'Référencement des publications utilisées
        'Element 1
        Set Pub1 = productPart1.Publications.Item("Droite")
        Set ref1 = Pub1.Valuation
        'Element 2
        Set Pub2 = productPart2.Publications.Item("DROITE_SECONDAIRE")
        Set ref2 = Pub2.Valuation
        'Mise en place de la contrainte
        Set constraint1 = constraints1.AddBiEltCst(catCstTypeDistance, ref1, ref2)
        'Contrainte de distance
        Set length1 = constraint1.Dimension
        
        If (moduleAssemble = "Placard_Haut_1." & nPH1) Then 'Placard Haut
            length1.Value = 1000 * -1 'TODO Mettre une valeur choisi par l'utilisateur
        ElseIf (moduleAssemble = "Bar." & nBA1) Then
            length1.Value = 0 * -1 'TODO mettre une valeur avec un offset
        Else
            length1.Value = prochainOffsetAngle * -1
            prochainOffsetAngle = moduleLargeur(numModule, 0)
            longueurSecondaire = moduleLargeur(numModule, 0)
        End If
        
        constraint1.Orientation = catCstOrientSame
        
        '
        'DERRIERE EN ANGLE
        '
        Set constraints1 = productMain.Connections("CATIAConstraints")
        'Référencement des publications utilisées
        'Element 1
        Set Pub3 = productPart1.Publications.Item("Derriere")
        Set ref3 = Pub3.Valuation
        'Element 2
        Set Pub4 = productPart2.Publications.Item("GAUCHE")
        Set ref4 = Pub4.Valuation
        'Mise en place de la contrainte
        Set constraint2 = constraints1.AddBiEltCst(catCstTypeDistance, ref3, ref4)
        'Contrainte de distance
        Set length2 = constraint2.Dimension
        
        If (moduleAssemble = "Bar." & nBA1) Then 'Bar
            length2.Value = 150  'TODO Mettre une valeur choisi par l'utilisateur
            constraint2.Orientation = catCstOrientOpposite
        Else
            length2.Value = 0
            constraint2.Orientation = catCstOrientSame
        End If
        
        
    Else
        MsgBox "Erreur sur l'emplacement d'assemblage du module : " & module(1, 0) & " / " & moduleAssemble
    End If
    
    '
    'DESSUS
    '
    Set constraints1 = productMain.Connections("CATIAConstraints")
    'Référencement des publications utilisées
    'Element 1
    If (moduleAssemble = "Placard_Haut_1." & nPH1) Then
        Set Pub5 = productPart1.Publications.Item("Dessous")
    Else
        Set Pub5 = productPart1.Publications.Item("Dessus")
    End If
    Set ref5 = Pub5.Valuation
    'Element 2
    Set Pub6 = productPart2.Publications.Item("DESSOUS")
    Set ref6 = Pub6.Valuation
    'Mise en place de la contrainte
    Set constraint3 = constraints1.AddBiEltCst(catCstTypeDistance, ref5, ref6)
    
    If (moduleAssemble = "Placard_Haut_1." & nPH1) Then 'Placard haut décallé en hauteur
        'Contrainte de distance
        Dim length3 As Length
        Set length3 = constraint3.Dimension
        length3.Value = 1200 * -1 'TODO Mettre une valeur choisi par l'utilisateur
        constraint3.Orientation = catCstOrientSame
    ElseIf (moduleAssemble = "Bar." & nBA1) Then
        Set length3 = constraint3.Dimension
        Call ExecuteCmd("SELECT Hauteur FROM bar WHERE IDClient =" & LancementConnexion.identifiant.Value)
        Call LectureSelect("Hauteur") 'lecture de la valeur demandé
        length3.Value = valeurLue * 1000 + 50
        constraint3.Orientation = catCstOrientOpposite
    Else
        constraint3.Orientation = catCstOrientOpposite
    End If
    
    
End Sub

Attribute VB_Name = "CuisineV2"
Sub CATMain()
    'affichage de la userform
    MiseAJour.Show
End Sub

Attribute VB_Name = "DataBase"
'Variables pour la connexion à la base de données
Private mDataBase As New ADODB.Connection
Private mRS As New ADODB.Recordset
Private mCmd As New ADODB.Command

'première dimension = numéro du module
'seconde dimension premier index = type de module
'seconde dimension second  index = position du module
'seconde dimension troisième index = largeur sur sa position
Public module(50, 6) As String
Public moduleLargeur(50, 1) As Integer

'Valeur retourné par la select
Public valeurLue As String

Sub CATMain() 'entrée du programme
    'debug
    LancementConnexion.log.Caption = LancementConnexion.log.Caption & " : En attente d'un identifiant utilisateur"
    LancementConnexion.log.Caption = "Système de connexion à la base prêt à lancer la mise à jour" & vbCrLf & LancementConnexion.log.Caption
    'affichage de la userform
    MiseAJour.Show
End Sub

Public Sub OpenConnection() 'connexion à la base de données au clique sur le bouton dans la useform
    'PS : pour lancer la connexion bien activer dans Tools>Référence :
    'Bibliothèque Microsoft ActiveX Data Objects 2.8
    'Bibliothèque de jeu d'enregistrements Microsoft ActiveX Data Objects 2.8

    'debug
    LancementConnexion.log.Caption = "Lancement de la requète de connexion à la base de données" & vbCrLf & LancementConnexion.log.Caption
    LancementConnexion.log.Caption = "Utilisation du protocole ADODB" & vbCrLf & LancementConnexion.log.Caption

    'connexion à la base de données
    Dim DB As String
    
    'Paramètre de connexion stocké sous forme de chaine
    'NE PAS diffuser cette partie CONFIDENTIELLE
    DB = "DRIVER={MySQL ODBC 5.1 Driver};" & _
        "SERVER=" & "185.11.204.104" & ";" & _
        "DATABASE=" & "iblkmqyy_cuisine" & ";" & _
        "USER=" & "iblkmqyy_cuisine" & ";" & _
        "PASSWORD=" & "Marmotte8" & ";"
        
    'ouverture
    mDataBase.Open DB
    'enregistrement de la connexion
    mCmd.ActiveConnection = mDataBase
    
    'debug
    LancementConnexion.log.Caption = "Test d'ouverture..." & vbCrLf & LancementConnexion.log.Caption
    
End Sub

Public Sub ExecuteCmd(sql As String) 'Execution des commandes SQL
    'debug
    LancementConnexion.log.Caption = "Préparation à l'envoi de la commande : " & sql & vbCrLf & LancementConnexion.log.Caption
    
    'enregistrement de la commande
    mCmd.CommandText = sql
    'envoi de la commande
    Set mRS = mCmd.Execute
    
    'debug
    LancementConnexion.log.Caption = "envoi..." & vbCrLf & LancementConnexion.log.Caption
End Sub

Public Sub LectureSelect(colonne As String) 'lecture de la base de données demandé en SELECT
    
    'debug
    LancementConnexion.log.Caption = "lecture des informations demandées..." & vbCrLf & LancementConnexion.log.Caption

    'affichage ligne par ligne tant qu'il y a des informations
    While mRS.EOF <> True
        
        'En cas de mise à jour de la référence en première étape
        If (colonne = "reference") Then 'pour la mise à jour de la référence
            Call MiseAJourReferenceAssemblageV2(mRS.Fields(colonne).Value)
        Else
            valeurLue = mRS.Fields(colonne).Value
        End If
        
        'normalement ne pas utiliser cette partie construire les commandes pour ne sortir une seule valeur
        If (mRS.EOF <> True) Then
            'ligne suivante
            Call mRS.MoveNext
        End If
        
    Wend
        
End Sub

Public Sub CloseConnection() 'Fermeture de la connexion avec la base de données à utiliser seulement en cas de problèmes ou en fin de mise à jour
    'debug
    LancementConnexion.log.Caption = "FERMETURE de la base de données" & vbCrLf & LancementConnexion.log.Caption
    
    'fermeture
    Call mDataBase.Close
    'nettoyage des variables pour une prochaine connexion propre
    Set mRS = Nothing
    Set mCmd = Nothing
    Set mDataBase = Nothing
    
    'debug
    LancementConnexion.log.Caption = "connexion interrompu, données de connexion supprimées" & vbCrLf & LancementConnexion.log.Caption
End Sub

Attribute VB_Name = "InsertionBarModele1"
Public Sub barModele1()
    'Paramètres du module
    Dim largeur As Integer
    Dim hauteur As Integer
    Dim profondeur As Integer
    Dim etagere As Integer
    
    'debug
    LancementConnexion.log.Caption = "insertion bar 1" & vbCrLf & LancementConnexion.log.Caption

    Dim productDocument1 As ProductDocument
    Set productDocument1 = CATIA.ActiveDocument
    
    Dim product1 As Product
    Set product1 = productDocument1.Product
    
    Dim products1 As Products
    Set products1 = product1.Products
    
    Dim arrayOfVariantOfBSTR1(0) 'Tableau pour stoker un chemin de fichier
    arrayOfVariantOfBSTR1(0) = CATIA.ActiveDocument.Path & "\Modules\Bar\Modele 1 bis\Bar.CATProduct" 'emplacement du module
    Set products1Variant = products1
    products1Variant.AddComponentsFromFiles arrayOfVariantOfBSTR1, "All" 'Chargement du module dans le product en cours

    Call ExecuteCmd("SELECT Largeur FROM bar WHERE IDClient =" & LancementConnexion.identifiant.Value)
    Call LectureSelect("Largeur") 'lecture de la valeur demandé
    Call MiseAJourParametreModule(3, "Largeur_bar", valeurLue) 'Mise à jour du paramètre
    
    'debug
    LancementConnexion.log.Caption = "Largeur : " & largeur & vbCrLf & LancementConnexion.log.Caption
    
    Call ExecuteCmd("SELECT Hauteur FROM bar WHERE IDClient =" & LancementConnexion.identifiant.Value)
    Call LectureSelect("Hauteur") 'lecture de la valeur demandé
    Call MiseAJourParametreModule(3, "Hauteur_bar", valeurLue) 'Mise à jour du paramètre
    
    'debug
    LancementConnexion.log.Caption = "Hauteur : " & hauteur & vbCrLf & LancementConnexion.log.Caption
    
    Call ExecuteCmd("SELECT Profondeur FROM bar WHERE IDClient =" & LancementConnexion.identifiant.Value)
    Call LectureSelect("Profondeur") 'lecture de la valeur demandé
    Call MiseAJourParametreModule(3, "Profondeur_bar", valeurLue) 'Mise à jour du paramètre
    
    'debug
    LancementConnexion.log.Caption = "Profondeur : " & profondeur & vbCrLf & LancementConnexion.log.Caption
    
End Sub

Attribute VB_Name = "InsertionPlacardBasModele1"
Public Sub placardBasModele1(position As String, numeroModule As Integer)
    'Paramètres du module
    Dim largeur As Integer
    Dim hauteur As Integer
    Dim profondeur As Integer
    Dim etagere As Integer
    
    'debug
    LancementConnexion.log.Caption = "insertion placard bas 1" & vbCrLf & LancementConnexion.log.Caption

    Dim productDocument1 As ProductDocument
    Set productDocument1 = CATIA.ActiveDocument
    
    Dim product1 As Product
    Set product1 = productDocument1.Product
    
    Dim products1 As Products
    Set products1 = product1.Products
    
    Dim arrayOfVariantOfBSTR1(0) 'Tableau pour stoker un chemin de fichier
    arrayOfVariantOfBSTR1(0) = CATIA.ActiveDocument.Path & "\Modules\Placard Bas\Modèle 1\Placard_Bas_1.CATProduct" 'emplacement du module
    Set products1Variant = products1
    products1Variant.AddComponentsFromFiles arrayOfVariantOfBSTR1, "All" 'Chargement du module dans le product en cours

    Call ExecuteCmd("SELECT largeur FROM placard_bas WHERE IDClient =" & LancementConnexion.identifiant.Value & " AND modele = 1")
    Call LectureSelect("largeur") 'lecture de la valeur demandé
    Call MiseAJourParametreModule(1, "Largeur_Placard", valeurLue) 'Mise à jour du paramètre
    
    If (position = "L") Then 'pour les lignes
        largeurAssemblageLigne = largeurAssemblageLigne + valeurLue * 1000 'Stockage du pramétre de largeur à i+1 pour le module suivant pour l'assemblage
    ElseIf (position = "A") Then 'pour les colonnes
        largeurAssemblageAngle = largeurAssemblageAngle + valeurLue * 1000 'Stockage du pramétre de largeur à i+1 pour le module suivant pour l'assemblage
    Else
        'debug
        LancementConnexion.log.Caption = "Module à assemblage spécifique" & vbCrLf & LancementConnexion.log.Caption
    End If
    'debug
    LancementConnexion.log.Caption = "Largeur : " & largeur & vbCrLf & LancementConnexion.log.Caption
    
    Call ExecuteCmd("SELECT hauteur FROM placard_bas WHERE IDClient =" & LancementConnexion.identifiant.Value & " AND modele = 1")
    Call LectureSelect("hauteur") 'lecture de la valeur demandé
    Call MiseAJourParametreModule(1, "Hauteur_Placard", valeurLue) 'Mise à jour du paramètre
    
    hauteurGeneral = hauteur * 1000
    
    'debug
    LancementConnexion.log.Caption = "Hauteur : " & hauteur & vbCrLf & LancementConnexion.log.Caption
    
    Call ExecuteCmd("SELECT profondeur FROM placard_bas WHERE IDClient =" & LancementConnexion.identifiant.Value & " AND modele = 1")
    Call LectureSelect("profondeur") 'lecture de la valeur demandé
    Call MiseAJourParametreModule(1, "Profondeur_Placard", valeurLue) 'Mise à jour du paramètre
    
    profondeurGeneral = valeurLue * 1000
    
    'debug
    LancementConnexion.log.Caption = "Profondeur : " & profondeur & vbCrLf & LancementConnexion.log.Caption
    
    Call ExecuteCmd("SELECT etagere FROM placard_bas WHERE IDClient =" & LancementConnexion.identifiant.Value & " AND modele = 1")
    Call LectureSelect("etagere") 'lecture de la valeur demandé
    Call MiseAJourParametreModule(1, "Nombre_Etageres", valeurLue) 'Mise à jour du paramètre
    
    'debug
    LancementConnexion.log.Caption = "Nombre d'étagère : " & etagere & vbCrLf & LancementConnexion.log.Caption
    
End Sub

Attribute VB_Name = "InsertionPlacardBasModele2"
Public Sub placardBasModele2(position As String, numeroModule As Integer)
    'Paramètres du module
    Dim largeur As Integer
    Dim hauteur As Integer
    Dim profondeur As Integer
    Dim etagere As Integer
    
    'debug
    LancementConnexion.log.Caption = "insertion placard bas 2" & vbCrLf & LancementConnexion.log.Caption

    Dim productDocument1 As ProductDocument
    Set productDocument1 = CATIA.ActiveDocument
    
    Dim product1 As Product
    Set product1 = productDocument1.Product
    
    Dim products1 As Products
    Set products1 = product1.Products
    
    Dim arrayOfVariantOfBSTR1(0) 'Tableau pour stoker un chemin de fichier
    arrayOfVariantOfBSTR1(0) = CATIA.ActiveDocument.Path & "\Modules\Placard Bas\Modèle 2\Placard_Bas_2.CATProduct" 'emplacement du module
    Set products1Variant = products1
    products1Variant.AddComponentsFromFiles arrayOfVariantOfBSTR1, "All" 'Chargement du module dans le product en cours

    Call ExecuteCmd("SELECT largeur FROM placard_bas WHERE IDClient =" & LancementConnexion.identifiant.Value & " AND modele = 2")
    Call LectureSelect("largeur") 'lecture de la valeur demandé
    Call MiseAJourParametreModule(2, "Largeur_Placard", valeurLue) 'Mise à jour du paramètre
    
    If (position = "L") Then 'pour les lignes
        largeurAssemblageLigne = largeurAssemblageLigne + valeurLue * 1000 'Stockage du pramétre de largeur à i+1 pour le module suivant pour l'assemblage
    ElseIf (position = "A") Then 'pour les colonnes
        largeurAssemblageAngle = largeurAssemblageAngle + valeurLue * 1000 'Stockage du pramétre de largeur à i+1 pour le module suivant pour l'assemblage
    Else
        'debug
        LancementConnexion.log.Caption = "Module à assemblage spécifique" & vbCrLf & LancementConnexion.log.Caption
    End If
    'debug
    LancementConnexion.log.Caption = "Largeur : " & largeur & vbCrLf & LancementConnexion.log.Caption
    
    Call ExecuteCmd("SELECT hauteur FROM placard_bas WHERE IDClient =" & LancementConnexion.identifiant.Value & " AND modele = 2")
    Call LectureSelect("hauteur") 'lecture de la valeur demandé
    Call MiseAJourParametreModule(2, "Hauteur_Placard", valeurLue) 'Mise à jour du paramètre
    
    hauteurGeneral = hauteur * 1000
    
    'debug
    LancementConnexion.log.Caption = "Hauteur : " & hauteur & vbCrLf & LancementConnexion.log.Caption
    
    Call ExecuteCmd("SELECT profondeur FROM placard_bas WHERE IDClient =" & LancementConnexion.identifiant.Value & " AND modele = 2")
    Call LectureSelect("profondeur") 'lecture de la valeur demandé
    Call MiseAJourParametreModule(2, "Profondeur_Placard", valeurLue) 'Mise à jour du paramètre
    
    profondeurGeneral = valeurLue * 1000
    
    'debug
    LancementConnexion.log.Caption = "Profondeur : " & profondeur & vbCrLf & LancementConnexion.log.Caption
    
    Call ExecuteCmd("SELECT etagere FROM placard_bas WHERE IDClient =" & LancementConnexion.identifiant.Value & " AND modele = 2")
    Call LectureSelect("etagere") 'lecture de la valeur demandé
    Call MiseAJourParametreModule(2, "Nombre_Etageres", valeurLue) 'Mise à jour du paramètre
    
    'debug
    LancementConnexion.log.Caption = "Nombre d'étagère : " & etagere & vbCrLf & LancementConnexion.log.Caption
    
End Sub

Attribute VB_Name = "InsertionPlacardHautModele1"
Public Sub placardHautModele1(position As String, numeroModule As Integer)
    'Paramètres du module
    Dim largeur As Integer
    Dim hauteur As Integer
    Dim profondeur As Integer
    Dim etagere As Integer
    
    'debug
    LancementConnexion.log.Caption = "insertion placard haut 1" & vbCrLf & LancementConnexion.log.Caption

    Dim productDocument1 As ProductDocument
    Set productDocument1 = CATIA.ActiveDocument
    
    Dim product1 As Product
    Set product1 = productDocument1.Product
    
    Dim products1 As Products
    Set products1 = product1.Products
    
    Dim arrayOfVariantOfBSTR1(0) 'Tableau pour stoker un chemin de fichier
    arrayOfVariantOfBSTR1(0) = CATIA.ActiveDocument.Path & "\Modules\Placard Haut\Modèle 1\Placard_Haut_1.CATProduct" 'emplacement du module
    Set products1Variant = products1
    products1Variant.AddComponentsFromFiles arrayOfVariantOfBSTR1, "All" 'Chargement du module dans le product en cours

    Call ExecuteCmd("SELECT largeur FROM placard_haut WHERE IDClient =" & LancementConnexion.identifiant.Value & " AND modele = 1")
    Call LectureSelect("largeur") 'lecture de la valeur demandé
    Call MiseAJourParametreModule(4, "Largeur_Placard", valeurLue) 'Mise à jour du paramètre
    
    'debug
    LancementConnexion.log.Caption = "Largeur : " & largeur & vbCrLf & LancementConnexion.log.Caption
    
    Call ExecuteCmd("SELECT hauteur FROM placard_haut WHERE IDClient =" & LancementConnexion.identifiant.Value & " AND modele = 1")
    Call LectureSelect("hauteur") 'lecture de la valeur demandé
    Call MiseAJourParametreModule(4, "Hauteur_Placard", valeurLue) 'Mise à jour du paramètre
    
    'debug
    LancementConnexion.log.Caption = "Hauteur : " & hauteur & vbCrLf & LancementConnexion.log.Caption
    
    Call ExecuteCmd("SELECT profondeur FROM placard_haut WHERE IDClient =" & LancementConnexion.identifiant.Value & " AND modele = 1")
    Call LectureSelect("profondeur") 'lecture de la valeur demandé
    Call MiseAJourParametreModule(4, "Profondeur_Placard", valeurLue) 'Mise à jour du paramètre
    
    'debug
    LancementConnexion.log.Caption = "Profondeur : " & profondeur & vbCrLf & LancementConnexion.log.Caption
    
    Call ExecuteCmd("SELECT etagere FROM placard_haut WHERE IDClient =" & LancementConnexion.identifiant.Value & " AND modele = 1")
    Call LectureSelect("etagere") 'lecture de la valeur demandé
    Call MiseAJourParametreModule(4, "Nombre_Etageres", valeurLue) 'Mise à jour du paramètre
    
    'debug
    LancementConnexion.log.Caption = "Nombre d'étagère : " & etagere & vbCrLf & LancementConnexion.log.Caption
    
End Sub

Attribute VB_Name = "LancementConnexion"
Attribute VB_Base = "0{E3B6F50C-88EE-4184-81C2-A817DB0F9265}{8C053F69-ED92-4823-8755-91D1249A816D}"
Attribute VB_GlobalNameSpace = False
Attribute VB_Creatable = False
Attribute VB_PredeclaredId = True
Attribute VB_Exposed = False
Attribute VB_TemplateDerived = False
Attribute VB_Customizable = False
Private Sub MiseAJour_Click()

    'Connexion à la base de données
    Call OpenConnection
    'Excution de la commande
    Call ExecuteCmd("SELECT reference FROM assemblage WHERE IDClient =" & LancementConnexion.identifiant.Value)
    'Lecture des données récupérées
    Call LectureSelect("reference")
    'Fermeture de la connexion
    Call CloseConnection
    
    'debug
    LancementConnexion.log.Caption = "Fin du protocole de mise à jour" & vbCrLf & LancementConnexion.log.Caption
End Sub

Attribute VB_Name = "LeGrandRemplacement"
Public Sub switch(ancienItem As String, cheminNouveau As String)
    Dim oRootProduct As Product
    Set oRootProduct = CATIA.ActiveDocument.Product
    
    If (ancienItem <> "Poignée_1.1") Then
        If (ancienItem = "Hotte.1") Then
            Set oRootProduct = CATIA.ActiveDocument.Product.Products.Item("Plaque_de_Cuisson_Hotte.1")
        End If
        
        Dim oldItem As Product
        Set oldItem = oRootProduct.Products.Item(ancienItem)
        
        Set oldItem = oRootProduct.Products.ReplaceComponent( _
                        oldItem, _
                        CATIA.ActiveDocument.Path & "\Modules\" & cheminNouveau, _
                        True)
    Else
        Set oRootProduct = CATIA.ActiveDocument.Product.Products.Item("Placard_Bas.1")
        
        Set oldItem = oRootProduct.Products.Item(ancienItem)
        
        Set oldItem = oRootProduct.Products.ReplaceComponent( _
                        oldItem, _
                        CATIA.ActiveDocument.Path & "\Pieds Poignées\" & cheminNouveau, _
                        True)
    End If
    
    Set oRootProduct = CATIA.ActiveDocument.Product
    oRootProduct.Update
End Sub

Attribute VB_Name = "MiseAJour"
Attribute VB_Base = "0{D92B8824-13BB-4C4D-857A-384225C876DC}{B5A0E6CB-E10A-46FC-B99B-C3414F1E63F4}"
Attribute VB_GlobalNameSpace = False
Attribute VB_Creatable = False
Attribute VB_PredeclaredId = True
Attribute VB_Exposed = False
Attribute VB_TemplateDerived = False
Attribute VB_Customizable = False
Private Sub GO_Click() 'Quand on clique sur le bouton pour tracker le client
    'Connexion à la base de données
    Call OpenConnection
    'Excution de la commande
    Call ExecuteCmd("SELECT reference FROM assemblage WHERE IDClient =" & MiseAJour.IDClient.Value)
    'Lecture des données récupérées
    Call LectureSelect("reference")
    'Fermeture de la connexion
    Call CloseConnection
End Sub

Attribute VB_Name = "MiseAJourReference"
'Mise à jour de la référence dans le squelette de l'assemblage
Public Sub MiseAJourReferenceAssemblageV2(reference As String)

    'debug
    LancementConnexion.log.Caption = "Mise à jour de la référence " & reference & vbCrLf & LancementConnexion.log.Caption

    Dim documents1 As Documents
    Set documents1 = CATIA.Documents
    
    Dim partDocument1 As PartDocument
    Set partDocument1 = documents1.Item("SqueletteAssemblage.CATPart")
    
    Dim part1 As Part
    Set part1 = partDocument1.Part
    
    Dim parameters1 As Parameters
    Set parameters1 = part1.Parameters
    
    Dim strParam1 As StrParam
    Set strParam1 = parameters1.Item("REFERENCE")
    
    'copie de la référence sur le paramètre CATIA
    strParam1.Value = "0000000"
    strParam1.Value = reference
    
    'différente variable présente dans la référence
    Dim longueur As Integer
    Dim largeur As Integer
    Dim cuisine As Integer
    Dim couleur As Integer
    Dim matiere As Integer
    Dim poignees As Integer
    Dim ilots As Integer
    Dim evier As Integer
    Dim hotte As Integer
    Dim bar As Integer
    
    'initialisation des variables
    longueur = -1
    largeur = -1
    cuisine = -1
    couleur = -1
    matiere = -1
    poignees = -1
    ilots = -1
    evier = -1
    hotte = -1
    bar = -1
    
    'récupération des valeurs dans la référence
    longueur = Mid(reference, 1, 1) * 1000 'multiplie par 1000 pour passer en mm
    If (longueur < 2332) Then 'sécurité minimum longueur
        longueur = 2332
    End If
    If (longueur > 5000) Then 'sécurité maximum longueur
        longueur = 5000
    End If
    largeur = Mid(reference, 2, 1) * 1000
    If (largeur < 2000) Then 'sécurité minimum largeur
        largeur = 2000
    End If
    If (largeur > 5000) Then 'sécurité maximum largeur
        largeur = 5000
    End If
    'séparateur T pour séparer les longueurs des options
    cuisine = Mid(reference, 4, 1)
    couleur = Mid(reference, 5, 1)
    matiere = Mid(reference, 6, 1)
    poignees = Mid(reference, 7, 1)
    ilots = Mid(reference, 8, 1)
    evier = Mid(reference, 9, 1)
    hotte = Mid(reference, 10, 1)
    bar = Mid(reference, 11, 1)
    
    Dim length1 As Length
    Set length1 = parameters1.Item("LONGUEUR_PRIMAIRE")
    length1.Value = longueur
    
    Set length1 = parameters1.Item("LONGUEUR_TERTIAIRE")
    length1.Value = longueur
    
    Set length1 = parameters1.Item("LONGUEUR_SECONDAIRE")
    length1.Value = largeur
    
    Set strParam1 = parameters1.Item("VERSION")
    
    If (cuisine = 0) Then
        strParam1.Value = "I"
    ElseIf (cuisine = 1) Then
        strParam1.Value = "L"
    ElseIf (cuisine = 2) Then
        strParam1.Value = "U"
    Else
        strParam1.Value = "ERREUR"
    End If
        
    Set strParam1 = parameters1.Item("COULEUR_MEUBLE")
    
    If (couleur = 0) Then
        strParam1.Value = "NOIR"
    ElseIf (couleur = 1) Then
        strParam1.Value = "CREME"
    ElseIf (couleur = 2) Then
        strParam1.Value = "ROUGE"
    Else
        strParam1.Value = "ERREUR"
    End If
    
    Set strParam1 = parameters1.Item("MATIERE_PLAN_TRAVAIL")
    
    If (matiere = 0) Then
        strParam1.Value = "BOIS"
    ElseIf (matiere = 1) Then
        strParam1.Value = "BETON"
    Else
        strParam1.Value = "ERREUR"
    End If
    
    Set strParam1 = parameters1.Item("POIGNEES")
    '9 modules à changer les poignées (6PB 2PH 1IL)
    If (poignees = 0) Then
        strParam1.Value = "MODERNE" 'MODERNE
        Call switch("Poignée_1.1", "Poignées\Poignee_1.CATPart")
    ElseIf (poignees = 1) Then
        strParam1.Value = "ARRONDIE" 'ARRONDIE
        Call switch("Poignée_1.1", "Poignées\Poignee_2.CATPart")
    Else
        strParam1.Value = "ERREUR"
    End If
    
    Set strParam1 = parameters1.Item("ILOT")
    
    If (ilots = 0) Then
        strParam1.Value = "NON"
    ElseIf (ilots = 1) Then
        strParam1.Value = "PORTES"
    ElseIf (ilots = 2) Then
        strParam1.Value = "TIROIRS"
    Else
        strParam1.Value = "ERREUR"
    End If
    
    Set strParam1 = parameters1.Item("EVIER")
    
    If (evier = 0) Then
        strParam1.Value = "SIMPLE_BAC"
        Call switch("Evier_double_robinet.1", "Appareils Standards\Evier\Evier + robinet.CATProduct")
    ElseIf (evier = 1) Then
        strParam1.Value = "DOUBLE_BAC"
        Call switch("Evier_double_robinet.1", "Appareils Standards\Evier\Evier_double_robinet.CATProduct")
    Else
        strParam1.Value = "ERREUR"
    End If
    
    Set strParam1 = parameters1.Item("HOTTE")
    
    If (hotte = 0) Then
        strParam1.Value = "TYPE 1"
        Call switch("Hotte.1", "Appareils Standards\Plaque de cuisson + Hotte\Hotte.CATPart")
    ElseIf (hotte = 1) Then
        strParam1.Value = "TYPE 2"
        Call switch("Hotte.1", "Appareils Standards\Plaque de cuisson + Hotte\Hotte_2.CATPart")
    ElseIf (hotte = 2) Then
        strParam1.Value = "TYPE 3"
        Call switch("Hotte.1", "Appareils Standards\Plaque de cuisson + Hotte\Hotte_3.CATPart")
    Else
        strParam1.Value = "ERREUR"
    End If
    
    Set strParam1 = parameters1.Item("BAR")
    
    If (bar = 0) Then
        strParam1.Value = "AUCUN"
    ElseIf (bar = 1) Then
        strParam1.Value = "OUI"
    Else
        strParam1.Value = "ERREUR"
    End If
    
    'décaler le module souple pour combler le trou sur le I
    Set partDocument1 = documents1.Item("Squelette_PB_1.CATPart")
    Set part1 = partDocument1.Part
    Set parameters1 = part1.Parameters
    Set length1 = parameters1.Item("Largeur_Placard")
    length1.Value = longueur - 2232
    
    Set partDocument1 = documents1.Item("Squelette_PB_2.CATPart")
    Set part1 = partDocument1.Part
    Set parameters1 = part1.Parameters
    Set length1 = parameters1.Item("Largeur_Placard")
    length1.Value = (longueur - ((longueur - 2232) * 2)) / 2
    
End Sub

Attribute VB_Name = "Module1"
Sub CATMain()

Dim productDocument1 As ProductDocument
Set productDocument1 = CATIA.ActiveDocument
Dim product1 As Product
Set product1 = productDocument1.Product
Set product1 = product1.ReferenceProduct
Dim products1 As Products
Set products1 = product1.Products

Dim product2 As Product
Set product2 = products1.Item("Placard_Bas.1")

Dim products2 As Products
Set products2 = product2.Products

Dim product3 As Product
Set product3 = products2.Item("Squelette_PB_1.1")

Dim products3 As Products
Set products3 = product3.Products

Dim constraints1 As Constraints
Set constraints1 = product1.Connections("CATIAConstraints")

Dim reference1 As reference
Set reference1 = product1.CreateReferenceFromName("Cuisine/Placard_Bas.1/Squelette_PB_1.1/!Dessus")

Dim reference2 As reference
Set reference2 = product1.CreateReferenceFromName("Cuisine/Plan de travail.2/!Plan xy")

Dim constraint1 As Constraint
Set constraint1 = constraints1.AddBiEltCst(catCstTypeDistance, reference1, reference2)

Dim length1 As Length
Set length1 = constraint1.Dimension

length1.Value = 0#

constraint1.Orientation = catCstOrientOpposite

Set product2 = products1.Item("Placard_Bas.1")

Set products2 = product2.Products

Set product3 = products2.Item("Squelette_PB_1.1")

Set products3 = product3.Products

Set constraints1 = product1.Connections("CATIAConstraints")

Dim reference3 As reference
Set reference3 = product1.CreateReferenceFromName("Cuisine/Placard_Bas.1/Squelette_PB_1.1/!Derriere")

Dim reference4 As reference
Set reference4 = product1.CreateReferenceFromName("Cuisine/Squelette.1/!DERRIERE")

Dim constraint2 As Constraint
Set constraint2 = constraints1.AddBiEltCst(catCstTypeDistance, reference3, reference4)

Dim length2 As Length
Set length2 = constraint2.Dimension

length2.Value = 0#

constraint2.Orientation = catCstOrientSame

Set product2 = products1.Item("Placard_Bas.1")

Set products2 = product2.Products

Set product3 = products2.Item("Squelette_PB_1.1")

Set products3 = product3.Products

Set constraints1 = product1.Connections("CATIAConstraints")

Dim reference5 As reference
Set reference5 = product1.CreateReferenceFromName("Cuisine/Placard_Bas.1/Squelette_PB_1.1/!Gauche")

Dim reference6 As reference
Set reference6 = product1.CreateReferenceFromName("Cuisine/Squelette.1/!GAUCHE_PRIMAIRE")

Dim constraint3 As Constraint
Set constraint3 = constraints1.AddBiEltCst(catCstTypeDistance, reference5, reference6)

Dim length3 As Length
Set length3 = constraint3.Dimension

length3.Value = 0#

constraint3.Orientation = catCstOrientSame

product1.Update

End Sub

Attribute VB_Name = "UpdateParametres"
'Mise à jour de la référence dans le squelette de l'assemblage
Public Sub MiseAJourReferenceAssemblage(reference As String)

    'debug
    LancementConnexion.log.Caption = "Mise à jour de la référence " & reference & vbCrLf & LancementConnexion.log.Caption

    Dim documents1 As Documents
    Set documents1 = CATIA.Documents
    
    Dim partDocument1 As PartDocument
    Set partDocument1 = documents1.Item("Squelette.CATPart")
    
    Dim part1 As Part
    Set part1 = partDocument1.Part
    
    Dim parameters1 As Parameters
    Set parameters1 = part1.Parameters
    
    Dim strParam1 As StrParam
    Set strParam1 = parameters1.Item("REFERENCE")
    
    'copie de la référence sur le paramètre CATIA
    strParam1.Value = "0000000"
    strParam1.Value = reference
    
    'Découpage de la référence pour intégrer les bons modules
    
    nombreModule = (Len(reference) / 5) - 1 'Calcul du nombre de module en fonction de la longueur de la référence
    'Mise à jour des premières largeurs pour commencer l'assemblage à l'origine
    largeurAssemblageAngle = 0
    largeurAssemblageLigne = 0
    
    Dim i As Integer
    
    For i = 0 To nombreModule
        'récupération de type de module
        module(i, 0) = Mid(reference, (i * 5) + 1, 1)
        'récupération de l'emplacement du module
        module(i, 1) = Mid(reference, (i * 5) + 2, 1)
        'option 1 : evier ou plaque de cuisson avec hote
        module(i, 2) = Mid(reference, (i * 5) + 3, 1)
        'option 2 : bar
        module(i, 3) = Mid(reference, (i * 5) + 4, 1)
        'option 3 : libre
        module(i, 4) = Mid(reference, (i * 5) + 5, 1)
        LancementConnexion.log.Caption = "Module " & i + 1 & " : " & module(i, 0) & " en position : " & module(i, 1) & vbCrLf & LancementConnexion.log.Caption
        
        'Selection du module à insérer
        Select Case module(i, 0)
            Case "1"
                'insérer un placard bas modèle 1
                Call placardBasModele1(module(i, 1), i)
                
                If (module(i, 1) = "L") Then 'pour les lignes
                    moduleLargeur(i, 0) = largeurAssemblageLigne
                ElseIf (module(i, 1) = "A") Then 'pour les colonnes
                    moduleLargeur(i, 0) = largeurAssemblageAngle
                End If
                
            Case "2"
                'insérer un placard bas modèle 2
                Call placardBasModele2(module(i, 1), i)
                
                If (module(i, 1) = "L") Then 'pour les lignes
                    moduleLargeur(i, 0) = largeurAssemblageLigne
                ElseIf (module(i, 1) = "A") Then 'pour les colonnes
                    moduleLargeur(i, 0) = largeurAssemblageAngle
                End If

            Case "3"
                'insérer un bar
            Case "4"
                'insérer un placard haut modèle 1
                Call placardHautModele1(module(i, 1), i)
            Case Else
                MsgBox "Erreur Numéro de module inconnu au moment de la découpe de la référence"
        End Select
        
    Next
    
    Call splitAssemblage 'Assemblage de tous les modules
    
    Call MiseAJourPlanDeTravail 'Mise à jour des dimensions du plan de travail
End Sub

Public Sub MiseAJourPlanDeTravail() 'Mise à jour des dimensions du plan de travail
    Dim productDocument1 As ProductDocument
    Set productDocument1 = CATIA.ActiveDocument
    
    Dim product1 As Product
    Set product1 = productDocument1.Product
    
    Set product1 = product1.ReferenceProduct
    
    Dim documents1 As Documents
    Set documents1 = CATIA.Documents
    
    Dim partDocument1 As PartDocument
    Set partDocument1 = documents1.Item("Squelette.CATPart")
    
    Dim part1 As Part
    Set part1 = partDocument1.Part
    
    Dim parameters1 As Parameters
    Set parameters1 = part1.Parameters
    
    'Mise à jour de la profondeur du plan de travail
    Dim length1 As Length
    Set length1 = parameters1.Item("PROFONDEUR")
    
    length1.Value = profondeurGeneral + 50
    
    'Mise à jour de la longueur primaire
    Set length1 = parameters1.Item("LONGUEUR_PRIMAIRE")
    
    length1.Value = longueurPrimaire + 50
    
    'Mise à jour de la longueur secondaire
    Set length1 = parameters1.Item("LONGUEUR_SECONDAIRE")
    
    length1.Value = longueurSecondaire + 50
    
    'Mise à jour de la hauteur
    Set length1 = parameters1.Item("HAUTEUR")
    
    length1.Value = hauteurGeneral
    
    'Vérification si cuisine en ligne ou en angle
    Dim boolParam1 As BoolParam
    Set boolParam1 = parameters1.Item("CUISINE_ANGLE")
    
    If (longueurSecondaire = 0) Then
        boolParam1.Value = False
    Else
        boolParam1.Value = True
    End If

    product1.Update 'Mise à jour de tout le produit

End Sub

'Mise à jour des paramètres de tous les modules appeller à chaque insertion de module avec les valeurs récupérées depuis le SELECT correspondant
Public Sub MiseAJourParametreModule(module As Integer, parametre As String, valeur As String)

    Dim nomCompletParametre As String 'chaine à coller dans le champs du paramètre
    
    nomCompletParametre = "Squelette_" 'Syntaxe normalement imposée sur tous les squelettes
    
    Select Case module 'à mettre à jour à chaque nousveau module
        Case 1
            'placard bas modèle 1
            nomCompletParametre = nomCompletParametre & "PB_1" & ".CATPart"
        Case 2
            'placard bas modèle 2
            nomCompletParametre = nomCompletParametre & "PB_2" & ".CATPart"
        Case 3
            'bar
            nomCompletParametre = nomCompletParametre & "BA_1" & ".CATPart"
        Case 4
            'insérer un placard haut modèle 1
            nomCompletParametre = nomCompletParametre & "PH_1" & ".CATPart"
        Case Else
            MsgBox "Erreur Numéro de module inconnu pour la mise à jour des paramètres"
    End Select
    
    'debug
    LancementConnexion.log.Caption = "Mise à jour de la référence " & reference & vbCrLf & LancementConnexion.log.Caption

    Dim documents1 As Documents
    Set documents1 = CATIA.Documents
    
    Dim partDocument1 As PartDocument
    Set partDocument1 = documents1.Item(nomCompletParametre)
    
    Dim part1 As Part
    Set part1 = partDocument1.Part
    
    Dim parameters1 As Parameters
    Set parameters1 = part1.Parameters
    
    'Tests selon le type de variable à mettre à jour
    If (parametre = "Nombre_Etageres") Then
        Dim intParam1 As IntParam
        Set intParam1 = parameters1.Item(parametre)
        
        intParam1.Value = valeur
    Else 'cas par défaut mise à jour d'une longueur
        Dim length1 As Length
        Set length1 = parameters1.Item(parametre)
        
        length1.Value = valeur * 1000
    End If

End Sub

Attribute VB_Name = "test"
Sub CATMain()

End Sub
